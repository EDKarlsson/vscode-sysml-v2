package ArgumentResolutionBug {
    class A {
        feature x;
    }
    
    behavior B  {
        in feature x;
        out feature : A = A(x);
    }
    
    class C {
        feature a : A;
        feature b : B;
        
        connector a :> a.x to b;
    }
}
