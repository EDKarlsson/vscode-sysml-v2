package Q {
    classifier F {
        feature a : A;
    }
      
    feature f : F;
      
    classifier A {
        feature g = f.a;
    }
      
    classifier B {
          feature f : F;
          feature a : A;
    }
      
    feature b : B {
          connector f.a to a.g;
          binding f.a = a.g;
    }
      
    feature g subsets f.a;
    subset g.g subsets b.f.a;
    redefinition b.f redefines b.a;
      
    subtype g.g specializes b.f.a;
    
    disjoint b.f.a from b.a;
    
}
